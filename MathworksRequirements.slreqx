# MathworksRequirements

## 1: Operable at major international airports (Functional)
The aircraft should be able to land, takeoff, and operate in major airports.
- Rationale: From the RFP document. Being able to operate, land, and takeoff at major international airports allows for more flexibility in flying routes.

### 2: Takeoff (Functional)
The aircraft should takeoff and land on runways of at least 8,000 feet.
- Rationale: From the RFP. The lower estimate for the average length of a runway is around 8,000 feet. The aircraft needs to accomodate for this takeoff and landing parameter to maintain diverse flight routes to satisfiy the customer.

### 3: Airport Gate Compatibility (Functional)
The aircraft should have gate compatibility with airports. Either FAA Aircraft Design Group 5 or ICAO Code E. (Requires wingspan to be less than 214 ft and tail height less than 66 ft)
- Rationale: From the RFP.

### 4: Taxiway Compatibility (Functional)
The aircraft should have airport taxiway compatibility. Twaxiway Design Group 6. (Requires outer-to-outer Main Gear Width (MGW) of 35-45 ft, and Cockpit (nose gear) to Main Gear distance of 100-125 ft).
- Rationale: From the RFP.

## 5: Cruise Speed (Functional)
The aircraft should have a minimum cuise speed of Mach 1.2. (Goal of Mach 1.8)
- Rationale: From the RFP.

## 6: Payload (Functional)
The aircraft should have a minimum payload capacity of 6 passengers. (Goal of 40 passengers).
- Rationale: From the RFP.

## 7: Range (Functional)
The aircraft should have a range of at least 2,000 nautical miles. (Goal of 5000 nautical miles).
- Rationale: From the RFP.

## 8: Noise Compliance (Functional)
The aircraft must adhere to the ICAO Chapter 14 limits. The sonic shock overland must be less than 75 EPNL (Effective Perceived Noise Level).
- Rationale: From the RFP.

## 9: Certification and Entry Into Service (Functional)
The aircraft must meet 14 CFR Part 25 (or equivalent international) certification standards. All components, including engines, must be certifiable by 2034. Target EIS: 2035.
- Rationale: From the RFP.

## 10: Weather Operations (Functional)
The aircraft should be capable in safe operations in all conditions, with emphasis on icy conditions.
- Rationale: From the RFP.

## 11: Compatible with SAFs (Functional)
The aircraft should be compatibile with sustainable aviation fuels (SAF).
- Rationale: From the RFP.

## 12: Cabin Comfort Features (Functional)
The cabin should be comfortable for passengers.
- Rationale: From the RFP.

### 13: Stand-up Cabin (Functional)
The cabin should have enough space for an average sized passenger to stand up.
- Rationale: From the RFP.

### 14: Space for Carry Ons (Functional)
The cabin should have compartments or space dedicated to luggage that passengers can carry onto the aircraft.
- Rationale: From the RFP.

## 15: Class Seating (Functional)
The aircraft should be capable of having a seating layout for at least two classes.
- Rationale: From the RFP.

## #50: Old requirements (subteams) (Functional)

### 16: Propulsion Requirements (Functional)
- Rationale: From comparator aircraft and market research.

#### 17: Fuel Type (Functional)
The aircraft should be compatiable with commonly used jet fuels. Common international and domestic jet fuels used include Jet A and Jet A-1.

#### 18: Thrust Requirement (Functional)
The aircraft should produce enough thrust to reach a minimum cruise speed of Mach 1.2. (Goal of Mach 1.8)

#### 20: ICAO Emissions (Functional)
The aircraft should fulfuill ICAO regulations on nitric oxide, nitrogen dioxide, and carbon dioxide emissions.

#### 19: Specific Fuel Consumption (Functional)
The aircraft should have a specific fuel consumption of less than or equal to 1.15 lb/lbf*hr (or 118 kg/kN*hr) at cruising speed.

### 20: Aerodynamic Requirements (Functional)
- Rationale: From comparator aircraft and market research.

#### 21: Wave Drag (Functional)
The wings should produce a wave drag as low as possible.

#### 22: Critical Mach Number (Functional)
The aircraft should have wings that result in a critical Mach number as high as possible.

#### 23: Glide Ratio (Functional)
The wings should provide a high glide ratio in subsonic and supersonic flight.

#### 24: Lift (Functional)
The lift gradient should be as high as possible so that higher approach speeds do not require large anlges of attack.

### 25: Weights and Balances Requirements (Functional)
- Rationale: From comparator aircraft and market research.

#### 26: Center of Gravity (Functional)
The center of gravity should maintain a constant position for the entirety of the flight.

#### 27: Weight Distribution (Functional)
The aircraft must be able to maintain proper weight distibution at any

#### 28: Turbulent Winds (Functional)
The wings and tail should be able to withstand turbulent winds withouth deformation.

#### 29: Enviormental Factor (Functional)
The materials used should be able to withstand any enviormental factors the plane should encounter

### 35: Systems Requirements (Functional)
- Rationale: From comparator aircraft and market research.

#### 37: Envelope Stability (Functional)
The aircraft should have a flight control system that satisfies the longitudinal and lateral-directional stability requirements through the flight envelope.

#### 38: Handling Quality (Functional)
The aircraft should have a Cooper-Harper handling rating at most a 2.

#### 36: Communication System (Functional)
The aircraft should have sufficient communications systems to maintain contact with air traffic control when crossing oceans and areas where signal jamming is used.

### 30: Stability and Control (Functional)
- Rationale: From comparator aircraft and market research.

#### 31: Static Margin (Functional)
The aircraft shall maintain a positive static margin through all flight segments.

#### 32: Climb Recovery (Functional)
The aircraft should recover from a high angle of attack climb.

#### 33: Control Surfaces (Functional)
The aircraft's control surfaces should maintain enough effectiveness while maintaining cruising speed.

#### 34: Deflection Limit (Functional)
The aircraft's control surfaces should have a maximum deflection limit to prevent loading issues.

### 39: Perfomance Requirements (Functional)

#### 40: Climb Rate (Functional)
The aircraft should have a climb rate of at least 3,500 feet per minute.

#### 41: Acceleration (Functional)
The aircraft should accelerate to a supersonic speed from takeoff in under 40 minutes.

#### 42: Cruise Altitude (Functional)
The aircraft should have a cruise altitude of at least 40,000 feet.

#### 43: One Engine Inoperative (Functional)
The aircraft should be controllable, takeoff, climb, cruise, and land while having one engine inoperative.
