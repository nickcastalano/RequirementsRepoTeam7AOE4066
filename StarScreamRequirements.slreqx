# StarScreamRequirements

## #1: Airport Gate Compatibility (Functional)
The aircraft should have gate compatibility with airports. Either FAA Aircraft Design Group 5 or ICAO Code E. (Requires wingspan to be less than 214 ft and tail height less than 66 ft)

## #2: Taxiway Compatibility (Functional)
The aircraft should have airport taxiway compatibility. Twaxiway Design Group 6. (Requires outer-to-outer Main Gear Width (MGW) of 35-45 ft, and Cockpit (nose gear) to Main Gear distance of 100-125 ft).

## #3: Takeoff (Functional)
The aircraft should takeoff and land on runways of at least 8,000 feet.

## #4: Cruise Speed (Functional)
The aircraft should have a minimum cuise speed of Mach 1.2. (Goal of Mach 1.8)

## #5: Passenger Count (Functional)
The aircraft should have a minimum payload capacity of 6 passengers. (Goal of 40 passengers).

## #6: Range (Functional)
The aircraft should have a range of at least 2,000 nautical miles. (Goal of 5000 nautical miles).

## #7: Noise Level (Functional)
The aircraft must adhere to the ICAO Chapter 14 limits. The sonic shock overland must be less than 75 EPNL (Effective Perceived Noise Level).

## #8: Certification and Entry into Service (Functional)
The aircraft must meet 14 CFR Part 25 (or equivalent international) certification standards. All components, including engines, must be certifiable by 2034. Target EIS: 2035.

## #9: Weather Operations (Functional)
The aircraft should be capable in safe operations in all conditions, with emphasis on icy conditions.

## #10: Compatible with SAFs (Functional)
The aircraft should be compatibile with sustainable aviation fuels (SAF).

## #11: Cabin Space (Functional)
The cabin should have enough space for an average sized passenger to stand up.

## #12: Baggage Space (Functional)
The cabin should have compartments or space dedicated to luggage that passengers can carry onto the aircraft.

## #13: Seating Space and Amenities (Functional)
The aircraft should be capable of having a seating layout for at least two classes.

## 14: Wing Requirements (Functional)

### #25: Lift at Cruise (Functional)
The wing shall generate enough lift to sustain steady level cruise at an alititude of 60,000 feet at Mach 1.8 and at maximum cruise weight.

### #32: Transonic (Functional)
The wing shall limit the drag increase during the transonic regime during acceleration from Mach 0.9 to Mach 1.2 so that the desired cruise speed can be achieved by the engine's thrust limits.

### #33: Lift at Takeoff (Functional)
The wing shall provide provide enough lift to meet takeoff and landing field length requirements at maximum takeoff and landing weights.

### #34: Wing load structure (Functional)
The wing's structures shall withstand limit loads without deformation and ultimate loads without failure.
- Rationale: FAA title 14 part 25 subpart c

### #35: Wing heating structure (Functional)
The wing shall withstand heating loads and expansion corresponding to sustained Mach 1.8 cruise.

### #39: Wing Volume (Functional)
The wings shall have an internal volume capable of housing fuel tanks, landing gear, and control surface mechanisms for the designed mission.

### #42: Wing weight structure (Functional)
The wing's strucutre shall withstand stress due to engine weight, fuel weight, and weight associated with control surface mechanisms through the entire flight envelope with a factor of safety.

### #44: Enviorment Protection (Functional)
The wing shall have the structural protection to withstand impact from bird strike, lightning strikes, and weather conditions during flight.

### #57: Roll Stability (Functional)
The wing shall provide sufficient stabilizing moment to ensure positive lateral static stability throughout the approved flight envelope.

### #60: Control Surface Reversal Prevention - Wing (Functional)
The wing structure shall maintain sufficient stiffness to prevent control surface reversal within the approved flight envelope.

## #17: Fuselage Requirements (Functional)

### #29: Fuselage structure (Functional)
The fuselage structure shall withstand limit loads without permanent deformation and ultimate loads without structural failure.

### #45: Fuselage heating and expansion (Functional)
The fuselage structure shall withstand heating loads and expansion associated with sustained cruise Mach without inducing structural failure or loss of pressurization.

### #46: Fuselage cabin volume (Functional)
The fuselage shall have sufficient volume to house a minimum of passengers 40 and associated baggage in the cabin.

### #47: Internal volume (Functional)
The fuselage shall have sufficient volume to house the necessary wiring, mechanical components, and baggage in the fuselage.

### #48: Cabin pressure (Functional)
The fuselage structure shall withstand loads associated with the pressurization of the cabin at the greatest pressure difference of the flight.

### #49: Aerodynamic performance (Functional)
The fuselage shall minimize drag to allow for a cruise of Mach 1.8

### #50: Emergency Exits (Functional)
The fuselage shall include sufficient emergency exits to allow evacuation of all passengers and crew under certification conditions.

### #51: Enviornment protection (Functional)
The fuselage shall have structural protection from enviormental effects including bird strikes, lighting strikes, and weather conditions during flight.

### #52: Transmitted loads (Functional)
The fuselage structure shall support loads transmitted from the wing and empennage without exceeding allowable structural limits.

## #18: Empennage Requirements (Functional)

### #30: Pitch Stability (Functional)
The empennage shall provide sufficient stabilizing moment to ensure positive longitudinal static stability throughout the approved flight envelope.

### #53: Yaw Stability (Functional)
The empennage shall provide sufficient directional stability such that the aircraft maintains positive weathercock stability throughout the approved flight envelope.

### #54: Empennage structure (Functional)
The empennage structure shall withstand limit loads without permanent deformation and ultimate loads without structural failure.

### #55: Empennage heating (Functional)
The empennage structure shall withstand heating loads and expanison associated with sustained supersonic cruise withou exceeding allowable material temperature limits.

### #56: Control Surface Reversal Prevention - Empennage (Functional)
The empennage structure shall maintain sufficient stiffness to prevent control surface reversal within the approved flight envelope.

### #61: Aerodynamic performance (Functional)
The empennage shall maintain stable aerodynamic performance when operating within the wake of upstream aircraft components.

### #62: Gust loads (Functional)
The empennage shall withstand gust loads encountered within the operational flight envelope without structural failure.

## #20: Flight Control System (Functional)

### #26: Yaw Control Authority (Functional)
The control surfaces shall provide sufficient yaw control authority at minimum approach speed and at cruise Mach number.

### #41: Roll Control Authority (Functional)
The control surfaces shall provide sufficient roll control authority at minimum approach speed and at cruise Mach number.

### #43: Pitch Control Authority (Functional)
The control surfaces shall provide sufficient pitch control authority at minimum approach speed and at cruise Mach number.

### #58: Control Effectiveness (Functional)
The control surfaces shall maintain adequate control effectiveness throughout the approved flight envelope.

### #59: O.E.I. Yaw Control (Functional)
The rudder shall provide sufficient control authority to maintain directional stability following the failure of the most critical engine during takeoff and climb.

### #64: Aerodynamic Performance (Functional)
The control surfaces shall allow the aircraft to maintain trimmed cruise flight without excessive control deflection that would significantly increase aerodynamic drag.

### #66: Actuators/hinge structures (Functional)
The control surface actuators and hinge structures shall withstand maximum hinge moments encountered throughout the flight envelope.

### #67: Deflection limits (Functional)
The control surfaces shall operate within defined deflection limits sufficient to maintain aircraft controllability throughout the flight envelope.

### #68: Control Respnsiveness (Functional)
The control surfaces shall respond to commanded inputs within a response time consistent with aircraft stability and handling quality requirements.

### #69: Actuator Failure Redundancy (Functional)
The control surface system shall maintain aircraft controllability following failure of any single actuator or control channel.

### #70: Handling qualities (Functional)
The flight control system shall provide aircraft handling qualities consistent with applicable civil transport aircraft standards.

### #71: Control During Flight regimes (Functional)
The flight control system shall maintain aircraft stability and controllability during transitions between subsonic, transonic, and supersonic flight regimes.

### #72: CG Shift Trim (Functional)
The flight control system shall maintain trim capability across the full approved center-of-gravity range.

### #73: Autopilot Capability (Functional)
The flight control system shall support autopilot functionality capable of maintaining commanded flight path parameters.

### #89: Engine Control (Functional)
The propulsion system shall include a control system capable of regulating engine thrust throughout the flight envelope.

## #21: Landing Gear System (Functional)

### #27: Load Capability (Functional)
The landing gear shall withstand landing loads associated with the maximum landing weight without structural failure.

### #74: General Operations (Functional)
The landing gear shall support the aircraft during ground operations, takeoff, and landing without exceeding allowable structural limits.

### #75: Retraction and Extension (Functional)
The landing gear shall retract fully into the aircraft structure and extend reliably throughout the operational flight envelope.

### #76: Breaks (Functional)
The landing gear braking system shall provide sufficient braking force to achieve the required landing stopping distance.

### #77: Impact Absorbtion (Functional)
The landing gear shall absorb landing impact energy without transmitting excessive loads to the aircraft structure.

### #78: Emergency Extension (Functional)
The landing gear shall include a mechanism for emergency deployment in the event of primary system failure.

## #22: Electrical and Avionics System (Functional)

### #28: Power Supply (Functional)
The electrical power system shall supply sufficient electrical power to all aircraft systems throughout all phases of flight.

### #80: Power System Redundancy (Functional)
The electrical power system shall include redundant power sources such that the failure of a single power source does not result in loss of critical avionics systems.

### #81: Avionics Accuracy (Functional)
The avionics system shall measure aircraft state parameters including altitude, airspeed, attitude, and position with accuracy sufficient to maintain safe aircraft navigation and control throughout the flight envelope.

### #82: Flight Navigation (Functional)
The avionics system shall provide navigation capability sufficient for operation along the planned flight route.

### #83: Flight Communication (Functional)
The avionics system shall provide reliable communication between the aircraft and air traffic control.

### #84: System Health Monitoring (Functional)
The avionics system shall monitor the health and status of critical aircraft systems and detect and report failures in avionics components and sensors

## #31: Propulsion System Requirements (Functional)

### 17: Fuel Type (Functional)
The propulsion system should be compatiable with commonly used jet fuels. Common international and domestic jet fuels used include Jet A and Jet A-1.

### 18: Cruise Thrust (Functional)
The propulsion system shall provide sufficient thrust to sustain steady cruise flight at Mach 1.8 and the design cruise altitude.

### #38: Fuel Consumption (Functional)
The propulsion system should have a fuel consumption to allow for the desired mission range.

### #85: Takeoff Thrust (Functional)
The propulsion system shall provide sufficient thrust to enable aircraft takeoff at maximum takeoff weight within the required takeoff field length.

### #86: Safety (Functional)
The propulsion system shall operate in all flight conditions and operations without compressor instability, unstart or surge.

### #87: Engine Loads (Functional)
The engine structure shall withstand aerodynamic, thermal, vibration, and inertial loads encountered during all phases of flight.

### #88: Noise Compliance (Functional)
The propulsion system shall comply with applicable aircraft noise regulations during takeoff, climb, and landing operations.
